SCHUGART-MIB DEFINITIONS ::= BEGIN

-- Imports
IMPORTS
    MODULE-IDENTITY, OBJECT-TYPE, NOTIFICATION-TYPE,
    Integer32, Unsigned32, Counter32, Counter64, TimeTicks, IpAddress,
    enterprises
        FROM SNMPv2-SMI
    TEXTUAL-CONVENTION, DisplayString
        FROM SNMPv2-TC
    MODULE-COMPLIANCE, OBJECT-GROUP, NOTIFICATION-GROUP
        FROM SNMPv2-CONF
    agentxObjects
        FROM AGENTX-MIB;

-- Description and update information                                                                                   
schugart MODULE-IDENTITY
    LAST-UPDATED "201405040000Z"
    ORGANIZATION "N/A"
    CONTACT-INFO
        "Editor:
        Dimitri Fagart
        EMail: <dimitri@schugart.net>"
    DESCRIPTION
        "schugart MIB for python-netsnmpagent"

    ::= { enterprises 43689  }

-- Definition of MIB's root nodes

raspberry         OBJECT IDENTIFIER ::= { schugart 1 }
ampliPower         OBJECT IDENTIFIER ::= { raspberry 1 }
dht22              OBJECT IDENTIFIER ::= { raspberry 2 }
dht22Ext            OBJECT IDENTIFIER ::= { dht22 1 }
dht22Cuisine        OBJECT IDENTIFIER ::= { dht22 2 }
dht22Sdb            OBJECT IDENTIFIER ::= { dht22 3 }
dht22Salon          OBJECT IDENTIFIER ::= { dht22 4 }
dht22Pc             OBJECT IDENTIFIER ::= { dht22 5 }
dht22Chambre        OBJECT IDENTIFIER ::= { dht22 6 }
dht22ChambreEnfant  OBJECT IDENTIFIER ::= { dht22 7 }
dht22Cave           OBJECT IDENTIFIER ::= { dht22 8 }
dht22ThermoOld      OBJECT IDENTIFIER ::= { dht22 9 }
dht22ThermoNew      OBJECT IDENTIFIER ::= { dht22 10 }
dht22SdbOld         OBJECT IDENTIFIER ::= { dht22 11 }
dht22SdbNew         OBJECT IDENTIFIER ::= { dht22 12 }
dht22Rasp           OBJECT IDENTIFIER ::= { dht22 13 }
cars               OBJECT IDENTIFIER ::= { raspberry 3 }
edf                OBJECT IDENTIFIER ::= { raspberry 4 }
fuel               OBJECT IDENTIFIER ::= { raspberry 5 }
discret            OBJECT IDENTIFIER ::= { raspberry 6 }
www               OBJECT IDENTIFIER ::= { schugart 2 }

------------------------------------------------------------------------
-- Scalars
------------------------------------------------------------------------

ampliCuisine OBJECT-TYPE
    SYNTAX      Integer32
    MAX-ACCESS  read-write
    STATUS      current
    DESCRIPTION
        "Ampli power state 0:Off  1:On"
    ::= { ampliPower 1 }

ampliChambre OBJECT-TYPE
    SYNTAX      Integer32
    MAX-ACCESS  read-write
    STATUS      current
    DESCRIPTION
        "Ampli power state 0:Off  1:On"
    ::= { ampliPower 2 }

ampliSdb OBJECT-TYPE
    SYNTAX      Integer32
    MAX-ACCESS  read-write
    STATUS      current
    DESCRIPTION
        "Ampli power state 0:Off  1:On"
    ::= { ampliPower 3 }

ampliSalon OBJECT-TYPE
    SYNTAX      Integer32
    MAX-ACCESS  read-write
    STATUS      current
    DESCRIPTION
        "Ampli power state 0:Off  1:On"
    ::= { ampliPower 4 }

dht22ExtTemp OBJECT-TYPE
    SYNTAX      Integer32
    MAX-ACCESS  read-only
    STATUS      current
    DESCRIPTION
        "sensor dht22 temperature"
    ::= { dht22Ext 1 }

dht22ExtHum OBJECT-TYPE
    SYNTAX      Integer32
    MAX-ACCESS  read-only
    STATUS      current
    DESCRIPTION
        "sensor dht22 humidity"
    ::= { dht22Ext 2 }

dht22CuisineTemp OBJECT-TYPE
    SYNTAX      Integer32
    MAX-ACCESS  read-only
    STATUS      current
    DESCRIPTION
        "sensor dht22 temperature"
    ::= { dht22Cuisine 1 }

dht22CuisineHum OBJECT-TYPE
    SYNTAX      Integer32
    MAX-ACCESS  read-only
    STATUS      current
    DESCRIPTION
        "sensor dht22 humidity"
    ::= { dht22Cuisine 2 }

dht22SdbTemp OBJECT-TYPE
    SYNTAX      Integer32
    MAX-ACCESS  read-only
    STATUS      current
    DESCRIPTION
        "sensor dht22 temperature"
    ::= { dht22Sdb 1 }

dht22SdbHum OBJECT-TYPE
    SYNTAX      Integer32
    MAX-ACCESS  read-only
    STATUS      current
    DESCRIPTION
        "sensor dht22 humidity"
    ::= { dht22Sdb 2 }

dht22SalonTemp OBJECT-TYPE
    SYNTAX      Integer32
    MAX-ACCESS  read-only
    STATUS      current
    DESCRIPTION
        "sensor dht22 temperature"
    ::= { dht22Salon 1 }

dht22SalonHum OBJECT-TYPE
    SYNTAX      Integer32
    MAX-ACCESS  read-only
    STATUS      current
    DESCRIPTION
        "sensor dht22 humidity"
    ::= { dht22Salon 2 }

dht22PcTemp OBJECT-TYPE
    SYNTAX      Integer32
    MAX-ACCESS  read-only
    STATUS      current
    DESCRIPTION
        "sensor dht22 temperature"
    ::= { dht22Pc 1 }

dht22PcHum OBJECT-TYPE
    SYNTAX      Integer32
    MAX-ACCESS  read-only
    STATUS      current
    DESCRIPTION
        "sensor dht22 humidity"
    ::= { dht22Pc 2 }

dht22ChambreTemp OBJECT-TYPE
    SYNTAX      Integer32
    MAX-ACCESS  read-only
    STATUS      current
    DESCRIPTION
        "sensor dht22 temperature"
    ::= { dht22Chambre 1 }

dht22ChambreHum OBJECT-TYPE
    SYNTAX      Integer32
    MAX-ACCESS  read-only
    STATUS      current
    DESCRIPTION
        "sensor dht22 humidity"
    ::= { dht22Chambre 2 }

dht22ChambreEnfantTemp OBJECT-TYPE
    SYNTAX      Integer32
    MAX-ACCESS  read-only
    STATUS      current
    DESCRIPTION
        "sensor dht22 temperature"
    ::= { dht22ChambreEnfant 1 }

dht22ChambreEnfantHum OBJECT-TYPE
    SYNTAX      Integer32
    MAX-ACCESS  read-only
    STATUS      current
    DESCRIPTION
        "sensor dht22 humidity"
    ::= { dht22ChambreEnfant 2 }

dht22CaveTemp OBJECT-TYPE
    SYNTAX      Integer32
    MAX-ACCESS  read-only
    STATUS      current
    DESCRIPTION
        "sensor dht22 temperature"
    ::= { dht22Cave 1 }

dht22CaveHum OBJECT-TYPE
    SYNTAX      Integer32
    MAX-ACCESS  read-only
    STATUS      current
    DESCRIPTION
        "sensor dht22 humidity"
    ::= { dht22Cave 2 }

dht22ThermoOldTemp OBJECT-TYPE
    SYNTAX      Integer32
    MAX-ACCESS  read-only
    STATUS      current
    DESCRIPTION
        "sensor dht22 temperature"
    ::= { dht22ThermoOld 1 }

dht22ThermoOldHum OBJECT-TYPE
    SYNTAX      Integer32
    MAX-ACCESS  read-only
    STATUS      current
    DESCRIPTION
        "sensor dht22 humidity"
    ::= { dht22ThermoOld 2 }

dht22ThermoNewTemp OBJECT-TYPE
    SYNTAX      Integer32
    MAX-ACCESS  read-only
    STATUS      current
    DESCRIPTION
        "sensor dht22 temperature"
    ::= { dht22ThermoNew 1 }

dht22ThermoNewHum OBJECT-TYPE
    SYNTAX      Integer32
    MAX-ACCESS  read-only
    STATUS      current
    DESCRIPTION
        "sensor dht22 humidity"
    ::= { dht22ThermoNew 2 }

dht22SdbOldTemp OBJECT-TYPE
    SYNTAX      Integer32
    MAX-ACCESS  read-only
    STATUS      current
    DESCRIPTION
        "sensor dht22 temperature"
    ::= { dht22SdbOld 1 }

dht22SdbOldHum OBJECT-TYPE
    SYNTAX      Integer32
    MAX-ACCESS  read-only
    STATUS      current
    DESCRIPTION
        "sensor dht22 humidity"
    ::= { dht22SdbOld 2 }

dht22SdbNewTemp OBJECT-TYPE
    SYNTAX      Integer32
    MAX-ACCESS  read-only
    STATUS      current
    DESCRIPTION
        "sensor dht22 temperature"
    ::= { dht22SdbNew 1 }

dht22SdbNewHum OBJECT-TYPE
    SYNTAX      Integer32
    MAX-ACCESS  read-only
    STATUS      current
    DESCRIPTION
        "sensor dht22 humidity"
    ::= { dht22SdbNew 2 }

dht22RaspTemp OBJECT-TYPE
    SYNTAX      Integer32
    MAX-ACCESS  read-only
    STATUS      current
    DESCRIPTION
        "sensor dht22 temperature"
    ::= { dht22Rasp 1 }

dht22RaspHum OBJECT-TYPE
    SYNTAX      Integer32
    MAX-ACCESS  read-only
    STATUS      current
    DESCRIPTION
        "sensor dht22 humidity"
    ::= { dht22Rasp 2 }

edfAdco OBJECT-TYPE
    SYNTAX      Counter64
    MAX-ACCESS  read-only
    STATUS      current
    DESCRIPTION
        "teleinfo label ADCO"
    ::= { edf 1 }

edfOptarif OBJECT-TYPE
    SYNTAX      DisplayString
    MAX-ACCESS  read-only
    STATUS      current
    DESCRIPTION
        "teleinfo label OPTARIF"
    ::= { edf 2 }

edfIsousc OBJECT-TYPE
    SYNTAX      Integer32
    MAX-ACCESS  read-only
    STATUS      current
    DESCRIPTION
        "teleinfo label ISOUSC"
    ::= { edf 3 }

edfBase OBJECT-TYPE
    SYNTAX      Integer32
    MAX-ACCESS  read-only
    STATUS      current
    DESCRIPTION
        "teleinfo label BASE"
    ::= { edf 4 }

edfPtec OBJECT-TYPE
    SYNTAX      Integer32
    MAX-ACCESS  read-only
    STATUS      current
    DESCRIPTION
        "teleinfo label PTEC"
    ::= { edf 5 }

edfIinst OBJECT-TYPE
    SYNTAX      Integer32
    MAX-ACCESS  read-only
    STATUS      current
    DESCRIPTION
        "teleinfo label IINST"
    ::= { edf 6 }

edfImax OBJECT-TYPE
    SYNTAX      Integer32
    MAX-ACCESS  read-only
    STATUS      current
    DESCRIPTION
        "teleinfo label IMAX"
    ::= { edf 7 }

edfPapp OBJECT-TYPE
    SYNTAX      Integer32
    MAX-ACCESS  read-only
    STATUS      current
    DESCRIPTION
        "teleinfo label PAPP"
    ::= { edf 8 }

edfIndexNormal OBJECT-TYPE
    SYNTAX      Integer32
    MAX-ACCESS  read-only
    STATUS      current
    DESCRIPTION
        "teleinfo label Index Normal"
    ::= { edf 9 }

edfIndexPointe OBJECT-TYPE
    SYNTAX      Integer32
    MAX-ACCESS  read-only
    STATUS      current
    DESCRIPTION
        "teleinfo label Index EJP"
    ::= { edf 10 }

edfIinst1 OBJECT-TYPE
    SYNTAX      Integer32
    MAX-ACCESS  read-only
    STATUS      current
    DESCRIPTION
        "teleinfo label IINST1"
    ::= { edf 11 }

edfIinst2 OBJECT-TYPE
    SYNTAX      Integer32
    MAX-ACCESS  read-only
    STATUS      current
    DESCRIPTION
        "teleinfo label IINST2"
    ::= { edf 12 }

edfIinst3 OBJECT-TYPE
    SYNTAX      Integer32
    MAX-ACCESS  read-only
    STATUS      current
    DESCRIPTION
        "teleinfo label IINST3"
    ::= { edf 13 }

edfPreavisEJP OBJECT-TYPE
    SYNTAX      Integer32
    MAX-ACCESS  read-only
    STATUS      current
    DESCRIPTION
        "teleinfo label Preavis EJP"
    ::= { edf 14 }

fuelBurningTime OBJECT-TYPE
    SYNTAX      Integer32
    MAX-ACCESS  read-only
    STATUS      current
    DESCRIPTION
        "fuel burning time"
    ::= { fuel 1 }

fuelBurnt OBJECT-TYPE
    SYNTAX      Integer32
    MAX-ACCESS  read-only
    STATUS      current
    DESCRIPTION
        "fuel burnt"
    ::= { fuel 2 }

fuelRemaining OBJECT-TYPE
    SYNTAX      Integer32
    MAX-ACCESS  read-only
    STATUS      current
    DESCRIPTION
        "fuel remaining"
    ::= { fuel 3 }

powerVMC OBJECT-TYPE
    SYNTAX      Integer32
    MAX-ACCESS  read-write
    STATUS      current
    DESCRIPTION
        "VMC power state 0:Off  1:On"
    ::= { discret 1 }

powerVentilo OBJECT-TYPE
    SYNTAX      Integer32
    MAX-ACCESS  read-write
    STATUS      current
    DESCRIPTION
        "Ventilo power state 0:Off  1:On"
    ::= { discret 2 }

contactThermo OBJECT-TYPE
    SYNTAX      Integer32
    MAX-ACCESS  read-write
    STATUS      current
    DESCRIPTION
        "Thermo contact state 0:Off  1:On"
    ::= { discret 3 }

logicalSpare1 OBJECT-TYPE
    SYNTAX      Integer32
    MAX-ACCESS  read-write
    STATUS      current
    DESCRIPTION
        "logical state 0:Off  1:On"
    ::= { discret 4 }

logicalSpare2 OBJECT-TYPE
    SYNTAX      Integer32
    MAX-ACCESS  read-write
    STATUS      current
    DESCRIPTION
        "logical state 0:Off  1:On"
    ::= { discret 5 }

discretState OBJECT-TYPE
    SYNTAX      Integer32
    MAX-ACCESS  read-write
    STATUS      current
    DESCRIPTION
        "logical state bit status"
    ::= { discret 6 }

ftpUser1 OBJECT-TYPE
    SYNTAX      Integer32
    MAX-ACCESS  read-write
    STATUS      current
    DESCRIPTION
        "Upload / Download speed from user 1"
    ::= { www 1 }

ftpUser2 OBJECT-TYPE
    SYNTAX      Integer32
    MAX-ACCESS  read-write
    STATUS      current
    DESCRIPTION
        "Upload / Download speed from user 2"
    ::= { www 2 }

ftpUser3 OBJECT-TYPE
    SYNTAX      Integer32
    MAX-ACCESS  read-write
    STATUS      current
    DESCRIPTION
        "Upload / Download speed from user 3"
    ::= { www 3 }

ftpUser4 OBJECT-TYPE
    SYNTAX      Integer32
    MAX-ACCESS  read-write
    STATUS      current
    DESCRIPTION
        "Upload / Download speed from user 4"
    ::= { www 4 }

ftpUser5 OBJECT-TYPE
    SYNTAX      Integer32
    MAX-ACCESS  read-write
    STATUS      current
    DESCRIPTION
        "Upload / Download speed from user 5"
    ::= { www 5 }

ftpUser6 OBJECT-TYPE
    SYNTAX      Integer32
    MAX-ACCESS  read-write
    STATUS      current
    DESCRIPTION
        "Upload / Download speed from user 6"
    ::= { www 6 }

END
